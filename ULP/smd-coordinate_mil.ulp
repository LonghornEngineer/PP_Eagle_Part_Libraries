#usage "<b>Print SMD coordinates for Top and Bottom</b>\n"
       "<p>"
       "Generates two files which contain the coordinates of the "
       "Smd pads in the layout. <i>Boardname.smt</i> for the Top layer, "
       "<i>boardname.smb</i> for Bottom layer. "
       "<p>"
       "<author>Author: support@cadsoft.de</author>"

// THIS PROGRAM IS PROVIDED AS IS AND WITHOUT WARRANTY OF ANY KIND, EXPRESSED OR IMPLIED

/*  SMD-coordinate.ulp erzeugt eine Datei "boardname.smt" fuer die Koordinaten
    der SMD-Pads auf der Bestueckungsseite (TOP)und eine Datei
    "boardname.smb" fuer die Koordinaten der SMD-Pads auf der
    Loetseite (BOTTOM).
    08.02.2001  alf@cadsoft.de
 */

int uval = 3;

string Version = "1.0.1";

int smdx[], smdy[];    // size of smd
int x[], y[];          // coordinate of SMD
int tb[];              // top or bottom side
string designator[];   // Parker Dillmann: Add designator to output file
int index[];
int c = 0;  // counter
string Boardname;
string fileTop;
string fileBottom;

  	int maxX = INT_MIN;
    int minX = INT_MAX;
    int maxY = INT_MIN;
    int minY = INT_MAX;

real value (int v) {
  return u2mil(v) ;
}

void  smdxy(int x, int y, string d) {
   printf("%s %5.2f %5.2f\n", d, value(x-minX), value(y-minY));
   return;
}

void genfiles(string file) {
  sort(c, index, tb, smdx, smdy, x, y, designator);  // sortiere top/bottom, groesse, coord.

  for (int n = 0; n < c; n++) {
    if (tb[index[n]]) {
      smdxy(x[index[n]], y[index[n]], designator[index[n]]);
      }
    else {
      output(fileTop, "at") {
        smdxy(x[index[n]], y[index[n]], designator[index[n]]);
        }
      }
    }
  }

// main

if (board) board(B) {
  Boardname = B.name;
	
	//Author: Parker Dillmann
	//Find boarder of file. 
	//This was we can set the origin of the boards XYRS data to (0,0).
	B.wires(W) 
	{
        if (W.layer == 20) 
		{
        if (W.x1 < minX) minX = W.x1;
        if (W.x2 < minX) minX = W.x2;
        if (W.x1 > maxX) maxX = W.x1;
        if (W.x2 > maxX) maxX = W.x2;
        if (W.y1 < minY) minY = W.y1;
        if (W.y2 < minY) minY = W.y2;
        if (W.y1 > maxY) maxY = W.y1;
        if (W.y2 > maxY) maxY = W.y2;
        }
    }
	//End what I have added. 

  fileTop = dlgFileSave("Save SMD coordinate for Top side", filesetext(B.name, ".smt"), "*.smt");
  if (fileTop == "") exit(0);

  fileBottom = dlgFileSave("Save SMD coordinate for Bottom side", filesetext(B.name, ".smb"), "*.smb");
  if (fileBottom == "") exit(0);

  output(fileTop, "wt");
  output(fileBottom, "wt") {
  
    B.elements(E) {
      E.package.contacts(C) {
        if (C.smd) {

           // collect SMD-Pads
           smdx[c] = C.smd.dx;
           smdy[c] = C.smd.dy;
           x[c] = C.smd.x;
           y[c] = C.smd.y;
           tb[c] = E.mirror;
		   designator[c] = E.name;
           c++;
        }
      }
    }

  genfiles(B.name);
  }
}


else {
   dlgMessageBox("\n    Start this ULP in a Board    \n");
   exit (0);
}
